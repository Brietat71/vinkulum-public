"""Exercise an installed FreeCAD workbench, not source-directory imports.

SPDX-License-Identifier: Apache-2.0
"""

import json
import os
import sys
import time
import traceback
from pathlib import Path

import FreeCAD as App
import FreeCADGui as Gui
from PySide6.QtCore import QProcess, QTimer, Qt
from PySide6.QtTest import QTest
from PySide6.QtWidgets import QApplication, QMessageBox

if App.listDocuments():
    raise RuntimeError("Use a dedicated empty FreeCAD session")
root = Path(os.environ["VINKULUM_FREECAD_CAPTURE"])
root.mkdir(parents=True, exist_ok=False)
report = {"status": "running", "freecad": App.Version(), "events": [], "trials": []}
state = {"finished": False, "doc": None}
watchdog = QTimer(Gui.getMainWindow())
watchdog.setSingleShot(True)


def save():
    (root / "report.json").write_text(json.dumps(report, indent=2) + "\n")


def finish(error=None):
    if state["finished"]:
        return
    state["finished"] = True
    watchdog.stop()
    report["status"] = "failed" if error else "passed"
    if error:
        report["error"] = str(error)
    save()
    vk = state.get("vk")
    if vk and vk._panel:
        vk._panel.reject()
    for name in list(App.listDocuments()):
        App.closeDocument(name)
    QTimer.singleShot(200, QApplication.instance().quit)


def caught(kind, error, trace):
    (root / "exception.log").write_text(
        "".join(traceback.format_exception(kind, error, trace))
    )
    finish(error)


sys.excepthook = caught


def unexpected_dialog(parent, title, message, *args, **kwargs):
    raise RuntimeError(f"Unexpected dialog {title}: {message}")


QMessageBox.warning = unexpected_dialog
watchdog.timeout.connect(lambda: finish("Qualification exceeded 90 seconds"))


def screenshot(name):
    Gui.updateGui()
    window = Gui.getMainWindow()
    assert (
        QApplication.primaryScreen().grabWindow(window.winId()).save(str(root / name))
    )


def wait_until(predicate, continuation):
    if state["finished"]:
        return
    if predicate():
        continuation()
    else:
        QTimer.singleShot(20, lambda: wait_until(predicate, continuation))


def start():
    try:
        assert "VinkulumWorkbench" in Gui.listWorkbenches()
        Gui.activateWorkbench("VinkulumWorkbench")
        import vinkulum_freecad as vk

        state["vk"] = vk
        report["installed_module"] = vk.__file__
        assert "/Mod/Vinkulum/" in vk.__file__
        report["installed_manifest"] = json.loads(
            (vk.ROOT / "build-info.json").read_text()
        )
        for name, digest in report["installed_manifest"]["sha256"].items():
            assert vk.bridge.sha((vk.ROOT / name).read_bytes()) == digest
        vk.preferences().SetString(
            "WorkerPython", os.environ["VINKULUM_FREECAD_PYTHON"]
        )
        vk.preferences().SetString("CalculationDirectory", str(root / "calculations"))
        Gui.getMainWindow().resize(1440, 950)
        Gui.runCommand("Vinkulum_Example")
        state["doc"] = App.ActiveDocument
        state["source"] = Gui.Selection.getSelection()[0]
        state["source_hash"] = vk.bridge.signature(state["source"])
        state["doc"].saveAs(str(root / "pendulum.FCStd"))
        save()
        Gui.runCommand("Vinkulum_Analysis")
        panel = state["panel"] = vk._panel
        assert panel is not None
        screenshot("opening.png")
        wait_until(panel.form.isVisible, panel_ready)
    except Exception as error:
        caught(type(error), error, error.__traceback__)


def panel_ready():
    panel = state["panel"]
    Gui.updateGui()
    Gui.activeDocument().activeView().fitAll(1.15)
    camera = Gui.activeDocument().activeView().getCameraOrientation()
    report["camera_orientation"] = list(camera.Q)
    report["source_bounds"] = str(state["source"].Shape.BoundBox)
    screenshot("analysis.png")
    QTest.mouseClick(panel.run_button, Qt.MouseButton.LeftButton)
    assert panel.job is not None
    wait_until(lambda: not panel.job.running, calculated)


def calculated():
    vk, panel = state["vk"], state["panel"]
    assert panel.record is not None, panel.status.text()
    request, result = panel.record
    assert abs(result["properties_si"]["mass_kg"] - 3.744) < 1e-10
    state["directory"] = panel.job.directory
    state["result_name"] = panel.result_object.Name
    report["capture_directory"] = str(panel.job.directory.relative_to(root))
    report["trials"].append(
        {
            "directory": report["capture_directory"],
            "length_mm": 800,
            "yaw_deg": 0,
            "axis": "Y",
            "pivot_mm": [0, 0, 0],
        }
    )
    report["events"].append("real_worker_completed")
    QTest.mouseClick(panel.play_button, Qt.MouseButton.LeftButton)
    assert panel.timer.isActive()
    wait_until(lambda: panel.slider.value() > 100, played)


def played():
    vk, panel = state["vk"], state["panel"]
    panel.stop()
    panel.slider.setValue(100)
    request, result = panel.record
    actual = list(panel.result_object.Shape.CenterOfMass)
    residual = max(
        abs(a * 0.001 - b) for a, b in zip(actual, result["position_m"][100])
    )
    assert residual < 1e-9, residual
    assert vk.bridge.signature(state["source"]) == state["source_hash"]
    report["centre_error_m"] = residual
    report["events"].append("native_samples_played_without_source_edit")
    screenshot("motion.png")
    Gui.runCommand("Std_Save")
    assert panel.reject()
    App.closeDocument(state["doc"].Name)
    state["doc"] = App.openDocument(str(root / "pendulum.FCStd"))
    obj = state["doc"].getObject(state["result_name"])
    Gui.Selection.clearSelection()
    Gui.Selection.addSelection(obj)
    Gui.runCommand("Vinkulum_Analysis")
    panel = state["panel"] = vk._panel
    assert panel is not None and panel.record is not None
    assert panel.record[0]["run_id"] == request["run_id"]
    panel.slider.setValue(200)
    actual = list(panel.result_object.Shape.CenterOfMass)
    assert (
        max(abs(a * 0.001 - b) for a, b in zip(actual, result["position_m"][200]))
        < 1e-9
    )
    report["events"].append("saved_document_and_result_reopened")
    state["variant"] = 0
    start_variant()


def start_variant():
    panel = state["panel"]
    variant = state["variant"]
    state["source"] = panel.source
    panel.source.Tip.Length = 1200
    yaw = 90 if variant == 0 else 0
    rotation = App.Rotation(App.Vector(0, 0, 1), yaw).multiply(
        App.Rotation(App.Vector(0, 1, 0), 160)
    )
    panel.source.Placement = App.Placement(App.Vector(100, -200, 300), rotation)
    state["doc"].recompute()
    # An old result still displays its own capture after a parametric edit.
    panel.slider.setValue(200)
    expected = panel.record[1]["position_m"][200]
    actual = list(panel.result_object.Shape.CenterOfMass)
    assert max(abs(a * 0.001 - b) for a, b in zip(actual, expected)) < 1e-9
    for field, value in zip(panel.pivot, (100, -200, 300)):
        field.setValue(value)
    panel.axis.setCurrentIndex(0 if variant == 0 else 2)
    state["variant_source_hash"] = state["vk"].bridge.signature(panel.source)
    state["variant_spec"] = {
        "length_mm": 1200,
        "yaw_deg": yaw,
        "axis": "X" if variant == 0 else "Z",
        "pivot_mm": [100, -200, 300],
    }
    QTest.mouseClick(panel.run_button, Qt.MouseButton.LeftButton)
    wait_until(lambda: not panel.job.running, variant_calculated)


def variant_calculated():
    panel = state["panel"]
    assert panel.record[0]["run_id"] == panel.job.request["run_id"], panel.status.text()
    assert abs(panel.record[1]["properties_si"]["mass_kg"] - 5.616) < 1e-10
    panel.slider.setValue(200)
    actual = list(panel.result_object.Shape.CenterOfMass)
    expected = panel.record[1]["position_m"][200]
    assert max(abs(a * 0.001 - b) for a, b in zip(actual, expected)) < 1e-9
    assert state["vk"].bridge.signature(panel.source) == state["variant_source_hash"]
    trial = state["variant_spec"] | {
        "directory": str(panel.job.directory.relative_to(root))
    }
    report["trials"].append(trial)
    report["events"].append(
        "parametric_recapture_and_translated_" + trial["axis"] + "_pivot"
    )
    if state["variant"] == 0:
        state["variant"] = 1
        QTimer.singleShot(0, start_variant)
        return
    state["doc"].saveAs(str(root / "translated.FCStd"))
    state["previous"] = panel.result_object
    state["previous_record"] = panel.record
    QTest.mouseClick(panel.run_button, Qt.MouseButton.LeftButton)
    wait_until(
        lambda: panel.job.process.state() == QProcess.ProcessState.Running, click_cancel
    )


def click_cancel():
    panel = state["panel"]
    report["cancel_running_pid"] = int(panel.job.process.processId())
    QTest.mouseClick(panel.cancel_button, Qt.MouseButton.LeftButton)
    wait_until(lambda: not panel.job.running, cancelled)


def cancelled():
    vk, panel = state["vk"], state["panel"]
    assert panel.record is state["previous_record"]
    assert panel.result_object is state["previous"]
    assert panel.play_button.isEnabled()
    assert not vk.bridge._active_jobs
    assert panel.job.process.state() == panel.job.process.ProcessState.NotRunning
    report["events"].append("cancellation_reaped_worker_and_retained_previous_result")
    QTest.mouseClick(panel.run_button, Qt.MouseButton.LeftButton)
    assert panel.job.running
    wait_until(
        lambda: panel.job.process.state() == QProcess.ProcessState.Running,
        close_running_document,
    )


def close_running_document():
    vk, panel = state["vk"], state["panel"]
    job = panel.job
    report["close_document_running_pid"] = int(job.process.processId())
    App.closeDocument(state["doc"].Name)
    wait_until(lambda: not job.running and vk._panel is None, closed)


def closed():
    assert not state["vk"].bridge._active_jobs
    report["events"].append("source_document_close_reaped_worker_and_closed_task")
    finish()


watchdog.start(90000)
QTimer.singleShot(600, start)
